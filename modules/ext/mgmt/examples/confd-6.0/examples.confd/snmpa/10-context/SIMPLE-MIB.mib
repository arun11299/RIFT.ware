SIMPLE-MIB DEFINITIONS ::= BEGIN

IMPORTS
    MODULE-IDENTITY, OBJECT-TYPE, NOTIFICATION-TYPE,
    Integer32, experimental
    	FROM SNMPv2-SMI
    DisplayString
        FROM SNMPv2-TC
    MODULE-COMPLIANCE, OBJECT-GROUP, NOTIFICATION-GROUP
        FROM SNMPv2-CONF;


simpleMIB MODULE-IDENTITY
    LAST-UPDATED "201101270000Z"
    ORGANIZATION "Tail-f Systems AB
                  http://www.tail-f.com"
    CONTACT-INFO
            "Tail-f support
             E-mail: support@tail-f.com"
    DESCRIPTION
            "Basic test objects for CONFD-SNMP integration."
    REVISION      "201101270000Z"
    DESCRIPTION
            "First version."
    ::= { experimental 1 }

-- Administrative assignments ++++---------------------------------

simpleMIBObjects	OBJECT IDENTIFIER ::= { simpleMIB 1 }
simpleMIBConformance    OBJECT IDENTIFIER ::= { simpleMIB 2 }

-- ----------------------------------------------------------------

variables     OBJECT IDENTIFIER ::= { simpleMIBObjects 1 }
tables        OBJECT IDENTIFIER ::= { simpleMIBObjects 2 }
notifications OBJECT IDENTIFIER ::= { simpleMIBObjects 3 }


testStr OBJECT-TYPE
    SYNTAX     DisplayString
    MAX-ACCESS  read-only
    STATUS      current
    DESCRIPTION    
            "This object exists in multiple contexts.

             When it is read, the value 'test-<context name>' is
             returned.."
    ::= { variables 1 }

-- Conformance ----------------------------------------------------
simpleMIBCompliances OBJECT IDENTIFIER ::= { simpleMIBConformance 1 }
simpleMIBGroups      OBJECT IDENTIFIER ::= { simpleMIBConformance 2 }


-- compliance statements

simpleMIBCompliance MODULE-COMPLIANCE
    STATUS  current
    DESCRIPTION
            "The compliance statement for SNMPv2 entities which
            implement the SNMPv2 MIB."
    MODULE  -- this module
        MANDATORY-GROUPS { thisGroup }

        GROUP   thisGroup
        DESCRIPTION
            "This group is mandatory for SNMPv2 entities which
            support community-based authentication."

    ::= { simpleMIBCompliances 2 }


-- units of conformance

thisGroup OBJECT-GROUP
    OBJECTS { 
    testStr
	     }
    STATUS  current
    DESCRIPTION
            "A collection of objects providing basic instrumentation and
            control of Servers."
    ::= { simpleMIBGroups 1 }


END
