module servers {
  namespace "http://tail-f.com/test/servers";
  prefix "srv";

  import ietf-inet-types {
    prefix inet;
  }
  import tailf-common {
    prefix tailf;
  }

  revision "2012-03-22";

  tailf:snmp-mib-module-name "SERVERS-MIB";
  tailf:snmp-oid "enterprises.24961.4";

  container servers {
    leaf ifmap {
      type binary;
      default "";
      tailf:hidden debug;
    }

    list server {
      key name;

      tailf:secondary-index "snmp" {
        tailf:index-leafs "index";
        tailf:sort-order "snmp";
      }
      tailf:snmp-name "srvServer";
      tailf:snmp-oid ".1";
      tailf:snmp-row-status-column 5;

      tailf:callpoint srv-hook {
        tailf:set-hook object;
      }

      leaf name {
        type string;
        tailf:snmp-oid ".2";
      }
      leaf index {
        type int32 {
          range "1..2147483647";
        }
        mandatory true;
        tailf:hidden debug;
        tailf:snmp-oid ".1";
        tailf:callpoint index-hook {
          tailf:transaction-hook subtree;
        }
      }
      leaf address {
        type inet:ipv4-address;
        tailf:snmp-oid ".3";
      }
      leaf description {
        type string;
        tailf:snmp-oid ".4";
      }

      leaf service-map {
        type binary;
        default "";
      }

      list service {
        key name;

        tailf:secondary-index "snmp" {
          tailf:index-leafs "index";
          tailf:sort-order "snmp";
        }
        tailf:snmp-name "srvService";
        tailf:snmp-oid ".2";
        tailf:snmp-row-status-column 4;
        tailf:callpoint service-hook {
          tailf:set-hook subtree;
        }

        leaf name {
          type string;
          tailf:snmp-oid ".2";
        }

        leaf index {
          type int32 {
            range "1..2147483467";
          }
          mandatory true;
          tailf:hidden debug;
          tailf:snmp-oid ".1";
          tailf:callpoint service-index-hook {
            tailf:transaction-hook subtree;
          }
        }

        leaf description {
          type string;
          tailf:snmp-oid ".3";
        }
      }
    }
  }
}
