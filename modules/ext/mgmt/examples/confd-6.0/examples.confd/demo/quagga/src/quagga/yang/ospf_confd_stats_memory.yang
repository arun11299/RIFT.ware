submodule ospf_confd_stats_memory {
  belongs-to quagga {
    prefix quagga;
  }

  include confd_top;
  include confd_common;

  import tailf-common {
    prefix tailf;
  }

/*  =============== memory statistics  ====================  */

  augment "/system/stats/memory" {

    container ospf {
      config false;
      tailf:callpoint ospfGetMemory;
      uses memoryStatusType;
    }
  }
}
