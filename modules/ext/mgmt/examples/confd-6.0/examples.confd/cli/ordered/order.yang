module order {
  namespace "http://tail-f.com/ns/example/order";
  prefix order;

  import ietf-inet-types {
    prefix inet;
  }

  import tailf-common {
    prefix tailf;
  }

  list server {
    key name;
    max-elements 64;
    tailf:indexed-view;
    leaf name {
      type int32;
    }
    leaf ip {
      type inet:ip-address;
      mandatory true;
    }
    leaf port {
      type inet:port-number;
      mandatory true;
    }
    leaf description {
      type string;
    }
  }

  list dns {
    key name;
    max-elements 64;
    ordered-by user;
    leaf name {
      type string;
    }
    leaf ip {
      type inet:ip-address;
      mandatory true;
    }
    leaf description {
      type string;
    }
  }

  list host {
    key name;
    max-elements 64;
    leaf name {
      type string;
    }
    leaf ip {
      type inet:ip-address;
      mandatory true;
    }
    leaf description {
      type string;
    }
  }
}
