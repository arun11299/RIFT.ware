module jdemo {
  namespace "http://tail-f.com/ns/example/jdemo";
  prefix jdemo;

  import ietf-inet-types {
    prefix inet;
  }
  import tailf-common {
    prefix tailf;
  }

  container arp {
    config false;
    tailf:callpoint jarp_data;
    list arpe {
      key "ip ifname";
      max-elements 1024;
      tailf:display-groups "none summary details";

      leaf ip {
        type inet:ip-address;
      }
      leaf ifname {
        type string;
      }
      leaf hwaddr {
        type string;
        mandatory true;
        tailf:display-groups "none summary details";
      }
      leaf permanent {
        type boolean;
        mandatory true;
        tailf:display-groups "none details";
      }
      leaf published {
        type boolean;
        mandatory true;
        tailf:display-groups "details";
      }
    }
  }
  container servers {
    list server {
      key name;
      max-elements 64;
      leaf name {
        type string;
      }
      leaf ip {
        type inet:ip-address;
        mandatory true;
        /*  validate the IP and warn for  */
        /*  certain subnets  */
        tailf:validate validateIp {
          tailf:dependency ".";
        }
      }
      leaf port {
        type inet:port-number;
        mandatory true;
        /*  check that port is unique and in range 1025-2048   */
        tailf:validate validatePort {
          tailf:dependency ".";
        }
      }
    }
  }
}
