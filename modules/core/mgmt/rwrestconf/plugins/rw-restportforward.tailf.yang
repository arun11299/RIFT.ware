/*
 * 
 * (c) Copyright RIFT.io, 2013-2016, All Rights Reserved
 *
 *
 */

module rw-restportforward-annotation
{
  namespace "http://riftio.com/ns/riftware-1.0/rw-restportforward-annotation";
  prefix "rw-restportforward-ann";

  import tailf-common {
    prefix tailf;
  }

  import rw-restportforward {
    prefix rw-restportforward;
  }

}
