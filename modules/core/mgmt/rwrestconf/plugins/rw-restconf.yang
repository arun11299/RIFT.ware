/*
 * 
 * (c) Copyright RIFT.io, 2013-2016, All Rights Reserved
 *
 *
 */

module rw-restconf
{
  namespace "http://riftio.com/ns/riftware-1.0/rw-restconf";
  prefix "rw-restconf";

  import rw-pb-ext {
    prefix "rwpb";
  }

  import rw-mgmt-schema {
    prefix "rw-mgmt-schema";
  }

  description "Rift RestConf Data Model";
  revision 2015-08-26 {
    description "Initial version"; 
  }

  container rwrestconf-configuration {
    rwpb:msg-new "RestconfConfig";  
    config true;

    leaf log-timing {
      type boolean;
    }
  }

  container rwrestconf-statistics {
    rwpb:msg-new Restconfstats;
    description "Restconf statistics";

    leaf get-req {
      type uint64;
    }

    leaf put-req {
      type uint64;
    }

    leaf post-req {
      type uint64;
    }

    leaf del-req {
      type uint64;
    }

    leaf get-200-rsp {
      type uint64;
    }

    leaf get-404-rsp {
      type uint64;
    }

    leaf get-500-rsp {
      type uint64;
    }

    leaf get-204-rsp {
      type uint64;
    }

    leaf put-200-rsp {
      type uint64;
    }

    leaf put-404-rsp {
      type uint64;
    }

    leaf put-500-rsp {
      type uint64;
    }

    leaf put-409-rsp {
      type uint64;
    }

    leaf put-405-rsp {
      type uint64;
    }

    leaf put-201-rsp {
      type uint64;
    }

    leaf post-200-rsp {
      type uint64;
    }

    leaf post-404-rsp {
      type uint64;
    }

    leaf post-500-rsp {
      type uint64;
    }

    leaf post-409-rsp {
      type uint64;
    }

    leaf post-405-rsp {
      type uint64;
    }

    leaf post-201-rsp {
      type uint64;
    }

    leaf del-405-rsp {
      type uint64;
    }

    leaf del-404-rsp {
      type uint64;
    }

    leaf del-500-rsp {
      type uint64;
    }

    leaf del-200-rsp {
      type uint64;
    }
  }


}
