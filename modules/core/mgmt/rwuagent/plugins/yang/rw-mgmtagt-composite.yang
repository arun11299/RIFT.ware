/*
 * 
 * (c) Copyright RIFT.io, 2013-2016, All Rights Reserved
 *
 */



/**
 * @file mgmtagt-composit.yang
 * @author Max Beckett
 * @date 2016/01/14
 * @brief Micro-agent local composite
 */

module rw-mgmtagt-composite
{
  namespace "http://riftio.com/ns/riftware-1.0/rw-mgmtagt-composite";
  prefix "rw-mgmtagt-composite";

  import rw-mgmtagt {
    prefix "rw-mgmtagt";
  }


  import rw-dts {
    prefix "rw-dts";
  }
  import rw-log {
    prefix "rw-log";
  }
  import rw-base {
    prefix "rw-base";
  }
  import rw-mgmt-schema {
    prefix "rw-mgmt-schema";
  }
  import rw-vcs {
    prefix "rw-vcs";
  }
  import rwlog-mgmt {
    prefix "rw-log-mgmt";
  }
  import rw-vnf-base-opdata {
    prefix "rw-vnf-base-opdata";
  }
  import rw-vnf-base-config {
    prefix "rw-vnf-base-config";
  }
  import mano-base {
    prefix "rw-mano-base";
  }
  import rw-memlog {
    prefix "rw-memlog";
  }
  import rw-manifest {
    prefix "rw-manifest";
  }
  
}
