/*
 * 
 * (c) Copyright RIFT.io, 2013-2016, All Rights Reserved
 *
 *
 */

module interfaces-tailf {

  namespace "http://riftio.com/ns/core/mgmt/rwuagent/test/interfaces-tailf";
  prefix "intf-tailf";

  import interfaces {
    prefix "interfaces";
  }

  import tailf-common {
    prefix "tailf";
  }

  tailf:annotate "/interfaces:interfaces/interfaces:interface/interfaces:status" {
    tailf:callpoint base_show;
  }

  tailf:annotate "/interfaces:clear-interface" {
    tailf:actionpoint rw_action;
  }

  tailf:annotate "/interfaces:raise-new-route" {
    tailf:actionpoint rw_action;
  }

  tailf:annotate "/interfaces:raise-temp-alarm" {
    tailf:actionpoint rw_action;
  }
}
