/*
 * 
 * (c) Copyright RIFT.io, 2013-2016, All Rights Reserved
 *
 *
 */

module rwmon
{
  namespace "http://riftio.com/ns/riftware-1.0/rwmon";
  prefix "rwmon";

  import rw-base {
    prefix rwbase;
  }

  import rw-pb-ext {
    prefix "rwpb";
  }

  import rw-yang-types {
    prefix "rwt";
  }

  import rw-log {
    prefix "rwlog";
  }

  import mano-types {
    prefix "manotypes";
  }

  revision 2015-10-28 {
    description
        "Initial revision.";
    reference
        "RIFT monitoring";
  }

  container nfvi-metrics {
    rwpb:msg-new NfviMetrics;

    uses manotypes:nfvi-metrics;
  }
}

/* vim: set ts=2:sw=2: */
