/*
 * 
 * (c) Copyright RIFT.io, 2013-2016, All Rights Reserved
 *
 *
 */

module rwmsg-data-tailf
{
  namespace "http://riftio.com/ns/riftware-1.0/rwmsg-data-tailf";
  prefix "rwmsg-data-tailf";

  import rwmsg-data {
    prefix "rwmsg";
  } 

  import tailf-common {
    prefix tailf;
  }

  tailf:annotate "/rwmsg:messaging" {
    tailf:callpoint base_show;
  }
}
