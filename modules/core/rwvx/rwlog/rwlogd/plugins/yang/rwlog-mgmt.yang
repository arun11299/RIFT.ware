/*
 * 
 * (c) Copyright RIFT.io, 2013-2016, All Rights Reserved
 *
 */



/**
 * @file rwlog.yang
 * @date 11/18/2014
 * @brief RiftWare CLI for Event log subsystem
 */

module rwlog-mgmt
{
  namespace "http://riftio.com/ns/riftware-1.0/rwlog-mgmt";
  prefix "rwlog-mgmt";

  import rw-pb-ext {
    prefix "rwpb";
  }
  import rw-log {
    prefix "rwlog";
  }
  import rw-yang-types {
    prefix "rwt";
  }
  import rw-cli-ext {
    prefix "rwcli";
  }
  import ietf-inet-types {
    prefix "inet";
   }
  revision 2014-08-11 {
    description
      "Initial revision.";
    reference
      "RIFT Event Logging Subsystem";
  }

  grouping event-filter {
    leaf event-Id {
      description "event Id";
      type uint64;
    } 
  }

  grouping event-rate {
    leaf value {
      description " number of logs per second";
      type uint32;
    }
  }

  container logging {
      rwcli:new-mode "logging";
      rwpb:msg-new Logging;
      description "Riftware Logging";
      leaf syslog-viewer {
        description "URL for syslog viewer used by UI";
         type inet:uri;
      } 
      uses rwlog:logging;
  }    

  rpc show-logs {
    description "Fetches Log events";
    input {
      uses rwlog:show-logs-input;
    }
    output {
      uses rwlog:show-logs-output;
    }
  }


  rpc log-event {
    description "Enable/Disable logging";
    input {
      choice method {
        case on {
          description "Enable Logging";
          leaf on {
            type empty;
          }
        }
        case off {
          description "Disable Logging";
          leaf off {
            type empty;
          }
        }
      }
      uses rwlog:vnf-identifiation;
      leaf checkpoint {
        description "checkpoint the current logs in the circular buffer";
        type empty;
      }
      container filter {
        description "rwlog filter settings";
        list category {
          key "name";
          uses rwlog:category-filter;
        }
        leaf callid {
          type uint64;
        }
        leaf groupcallid {
          type uint64;
        }
        leaf protocol {
          type rwlog:protocol_type;
        }  
        uses rwlog:session-grp-params;
        leaf failed-call-recording {
          type rwlog:on_off_type;
        }
        leaf next-call {
          type rwlog:on_off_type;
        }
        leaf next-failed-call {
          type rwlog:on_off_type;
        }
        container deny {
          list event {
            description "event symbolic name";
            key "event-Id";
            uses event-filter;
          }
        } // deny
        leaf hostname {
          description "apply filter only for this hostname";
          type string;
        }
      }
    }
  }

}
