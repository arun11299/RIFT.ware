/* STANDARD-RIFT-IO-COPYRIGHT */
/**
 * @file   rw-dts-router-log.yang
 * @author Rajesh Velandy
 * @date   2014/12/22
 * @brief  Riftware yang data schema for DTS Router logging
 */

module rw-dts-router-log
{
  namespace "http://riftio.com/ns/riftware-1.0/rwdtsrouterlog";
  prefix "rwdtsrouterlog";

  import rw-base {
    prefix rwbase;
  }

  import rw-pb-ext {
    prefix "rwpb";
  }

  import rw-yang-types {
    prefix "rwt";
  }

  import rw-notify-ext {
    prefix "rwnotify";
  }

  import rw-log {
    prefix "rwlog";
  }

  description "RW.DTS ROUTER logging definitions";

  revision 2014-12-22 {
    description "Initial revision";
    reference "Rift Yang Data schema for DTS ROUTER Logging";
  }

  grouping dtsrouter-gen-attr {
    description "Grouping for generic router events";
    leaf router-name {
      type string;
      description "Name of the dts router";
    }
  }

  grouping dtsrouter-reg-attr {
    description "Grouping for router registration events";
    uses dtsrouter-gen-attr;

    leaf member-name {
      type string;
      description "Name of the dts member";
    }
  }

  grouping dtsrouter-xact-attr {

    description "Grouping for transaction events";

    uses dtsrouter-gen-attr;

    leaf xact-id {
      description "DTS transaction id";
      type string;
    }
  }

  grouping dtsrouter-member-xact-attr {

    description "Grouping for member transaction events";

    leaf member-name {
      description "DTS member name";
      type string;
    }

    leaf query-idx {
      description "Query Id";
      type uint32;
    }

    leaf query-serial {
      description "Query Serial";
      type uint32;
    }
  }

  notification dtsrouter-debug {
    rwnotify:log-event-id 00040000;
    description "DTS Router generic debug log";
    uses rwlog:severity-debug;
    leaf log {
      type string;
    }
    uses dtsrouter-gen-attr;
  }

  notification dtsrouter-info {
    rwnotify:log-event-id 00040001;
    description "DTS Router generic info log";
    uses rwlog:severity-info;
    leaf log {
      type string;
    }
    uses dtsrouter-gen-attr;
  }

  notification dtsrouter-notice {
    rwnotify:log-event-id 00040002;
    description "DTS Router generic notice log";
    uses rwlog:severity-notice;
    leaf log {
      type string;
    }
    uses dtsrouter-gen-attr;
  }
  notification dtsrouter-warning {
    rwnotify:log-event-id 00040003;
    description "DTS Router generic warning log";
    uses rwlog:severity-warning;
    leaf log {
      type string;
    }
    uses dtsrouter-gen-attr;
  }

  notification dtsrouter-error {
    rwnotify:log-event-id 00040004;
    description "DTS Router generic error log";
    uses rwlog:severity-error;
    leaf log {
      type string;
    }
    uses dtsrouter-gen-attr;
  }

  notification dtsrouter-critical {
    rwnotify:log-event-id 00040005;
    description "DTS Router generic critical log";
    uses rwlog:severity-critical;
    leaf log {
      type string;
    }
    uses dtsrouter-gen-attr;
  }

  notification dtsrouter-alert {
    rwnotify:log-event-id 00040006;
    description "DTS Router generic alert log";
    uses rwlog:severity-alert;
    leaf log {
      type string;
    }
    uses dtsrouter-gen-attr;
  }

  notification dtsrouter-emergency {
    rwnotify:log-event-id 00040007;
    description "DTS Router generic emergency log";
    uses rwlog:severity-emergency;
    leaf log {
      type string;
    }
    uses dtsrouter-gen-attr;
  }

  notification msg-regist {
    rwnotify:log-event-id 00040008;
    description "DTS Router got regist message";
    uses rwlog:severity-debug;
    leaf log {
      type string;
    }
  }

  notification msg-execute {
    rwnotify:log-event-id 00040009;
    description "DTS Router got execute message";
    uses rwlog:severity-debug;
    leaf log {
      type string;
    }
  }

  notification msg-end {
    rwnotify:log-event-id 00040010;
    description "DTS Router got end message";
    uses rwlog:severity-debug;
    leaf log {
      type string;
    }
  }

  notification msg-abort {
    rwnotify:log-event-id 00040011;
    description "DTS Router got abort message";
    uses rwlog:severity-debug;
    leaf log {
      type string;
    }
  }

  notification msg-flush {
    rwnotify:log-event-id 00040012;
    description "DTS Router got flush message";
    uses rwlog:severity-debug;
    leaf log {
      type string;
    }
  }

  notification added-member-reg {
    rwnotify:log-event-id 00040013;
    description "Router added a member registration";
    uses rwlog:severity-debug;
    leaf log {
      type string;
    }
    uses dtsrouter-reg-attr;

    leaf key-spec {
      description "keyspec in registration";
      type string;
    }
  }


  notification member-already-present {
    rwnotify:log-event-id 00040014;
    description "DTS router ignoring reg request - member already present";
    uses rwlog:severity-info;
    leaf log {
      type string;
    }
    uses dtsrouter-reg-attr;
  }

  notification member-rcvd-empty-name {
    rwnotify:log-event-id 00040015;
    description "DTS router received reg/dereg with empty name";
    uses rwlog:severity-critical;
    leaf log {
      type string;
    }
    uses dtsrouter-reg-attr;
  }

  notification dereg-member-not-found {
    rwnotify:log-event-id 00040016;
    description "DTS router received dereg - no matching member found";
    uses rwlog:severity-error;
    leaf log {
      type string;
    }
    uses dtsrouter-reg-attr;
  }

  notification member-deregistered {
    rwnotify:log-event-id 00040017;
    description "DTS router deregistering member";
    uses rwlog:severity-info;
    uses dtsrouter-reg-attr;
    leaf log {
      type string;
    }
  }

  notification router-started {
    rwnotify:log-event-id 00040018;
    description "DTS router deregistering member";
    uses rwlog:severity-info;
    uses dtsrouter-gen-attr;
    leaf log {
      type string;
    }
  }

  notification router-state-init {
    rwnotify:log-event-id 00040019;
    description "DTS router state init";
    uses rwlog:severity-debug;
    uses dtsrouter-xact-attr;

    leaf log {
      type string;
    }
  }

  notification router-state-destroy {
    rwnotify:log-event-id 00040020;
    description "DTS router state destroy";
    uses rwlog:severity-debug;
    uses dtsrouter-xact-attr;

    leaf life-time {
      type int32;
    }
    leaf log {
      type string;
    }
  }

  notification query-rsp-member {
    rwnotify:log-event-id 00040021;
    description "Query response from member";
    uses rwlog:severity-debug;
    uses dtsrouter-xact-attr;

    leaf log {
      description "Log message";
      type string;
    }

    uses dtsrouter-member-xact-attr;
  }

  notification no-query-rsp-member {
    rwnotify:log-event-id 00040022;
    description "No query result, using top level xact  ";
    uses rwlog:severity-error;
    uses dtsrouter-xact-attr;


    leaf log {
      description "Log message";
      type string;
    }

    leaf evtrsp {
      description "Query event rsp";
      type uint32;
    }

    uses dtsrouter-member-xact-attr;
  }

  notification malformed-query-result {
    rwnotify:log-event-id 00040023;
    description "Malformed query result";
    uses rwlog:severity-error;
    uses dtsrouter-xact-attr;

    leaf log {
      description "Log message";
      type string;
    }

    uses dtsrouter-member-xact-attr;
  }

  notification unexpected-query-result {
    rwnotify:log-event-id 00040024;
    description "Unexpected query result";
    uses rwlog:severity-error;
    uses dtsrouter-xact-attr;

    leaf log {
      description "Log message";
      type string;
    }

    leaf state {
      description "DTS router state";
      type uint32;
    }

    uses dtsrouter-member-xact-attr;
  }

  notification query-result-async {
    rwnotify:log-event-id 00040026;
    description "async query result";
    uses rwlog:severity-debug;
    uses dtsrouter-xact-attr;

    leaf log {
      description "Log message";
      type string;
    }

    leaf state {
      description "DTS router state";
      type uint32;
    }

    uses dtsrouter-member-xact-attr;
  }
  
  notification query-result-ack {
    rwnotify:log-event-id 00040027;
    description "ack query result";
    uses rwlog:severity-debug;

    uses dtsrouter-xact-attr;

    leaf log {
      description "Log message";
      type string;
    }

    leaf state {
      description "DTS router state";
      type uint32;
    }

    uses dtsrouter-member-xact-attr;
  }

  notification query-result-na {
    rwnotify:log-event-id 00040028;
    description "na query result";
    uses rwlog:severity-debug;
    uses dtsrouter-xact-attr;

    leaf log {
      description "Log message";
      type string;
    }

    leaf state {
      description "DTS router state";
      type uint32;
    }

    uses dtsrouter-member-xact-attr;
  }

  notification query-result-nack {
    rwnotify:log-event-id 00040029;
    description "nack query result";
    uses rwlog:severity-info;
    uses dtsrouter-xact-attr;

    leaf log {
      description "Log message";
      type string;
    }

    leaf state {
      description "DTS router state";
      type uint32;
    }

    uses dtsrouter-member-xact-attr;
  }

  notification query-result-error {
    rwnotify:log-event-id 00040030;
    description "error query result";
    uses rwlog:severity-error;
    uses dtsrouter-xact-attr;

    leaf log {
      description "Log message";
      type string;
    }

    leaf state {
      description "DTS router state";
      type uint32;
    }

    uses dtsrouter-member-xact-attr;
  }

  notification xact-union-size {
    rwnotify:log-event-id 00040031;
    description "xact union size";
    uses rwlog:severity-debug;
    uses dtsrouter-xact-attr;

    leaf log {
      description "Log message";
      type string;
    }

    leaf union-size {
      description "xact union size";
      type uint32;
    }
  }

  notification xact-evt-rsp-member {
    rwnotify:log-event-id 00040032;
    description "xact event response";
    uses rwlog:severity-debug;
    uses dtsrouter-xact-attr;

    leaf log {
      description "Log message";
      type string;
    }

    uses dtsrouter-member-xact-attr;
  }

  notification unexpected-bounce-response {
    rwnotify:log-event-id 00040036;
    description "Unxecpected bounce response";
    uses rwlog:severity-error;
    uses dtsrouter-gen-attr;

    leaf log {
      description "Log message";
      type string;
    }
  }

  notification member-bounce {
    rwnotify:log-event-id 00040036;
    description "member response bounced";
    uses rwlog:severity-info;
    uses dtsrouter-gen-attr;

    leaf log {
      description "Log message";
      type string;
    }
  }

  notification response-rcvd {
    rwnotify:log-event-id 00040037;
    description "member received response from router";
    uses rwlog:severity-debug;
    uses dtsrouter-xact-attr;

    leaf log {
      description "Log message";
      type string;
    }
    leaf num-result {
      description "number of results";
      type uint32;
    }
  }

  notification xact-mismatched-rsp {
    rwnotify:log-event-id 00040038;
    description "member received mismatched response from router";
    uses rwlog:severity-error;

    uses dtsrouter-xact-attr;

    leaf log {
      description "Log message";
      type string;
    }
    leaf xreq-id {
      description "xreq id";
      type int32;
    }
    leaf query-id{
      description "xreq id";
      type uint32;
    }
    leaf query-serial {
      description "query serial";
      type uint32;
    }
    leaf req-query-serial {
      description "query serial";
      type uint32;
    }
    leaf req {
      description "req";
      type uint64;
    }
    leaf rsp-req {
      description "rsp req";
      type uint64;
    }
    leaf req-state {
      description "req state";
      type int32;
    }
  }

  notification brute-force-found {
    rwnotify:log-event-id 00040039;
    description "member received mismatched response from router";
    uses rwlog:severity-warning;

    uses dtsrouter-xact-attr;

    leaf log {
      description "Log message";
      type string;
    }
    leaf xreq-id {
      description "xreq id";
      type int32;
    }
    leaf query-serial {
      description "query serial";
      type uint32;
    }
    leaf member-name  {
      description "member name";
      type string;
    }
  }

  notification unable-to-correlate {
    rwnotify:log-event-id 00040040;
    description "Unable to correlate rsp in xact";
    uses rwlog:severity-error;

    uses dtsrouter-xact-attr;

    leaf log {
      description "Log message";
      type string;
    }
    leaf rsp_req  {
      description "rsp req";
      type uint64;
    }
  }

  notification uncorrelated-query-result {
    rwnotify:log-event-id 00040041;
    description "Uncorrelated query result";
    uses rwlog:severity-error;

    uses dtsrouter-xact-attr;

    leaf log {
      description "Log message";
      type string;
    }
    leaf hasquery-id {
      description "has query id";
      type uint32;
    }
    leaf query-id {
      description "query id";
      type uint32;
    }
  }

  notification uncorrelated-block-result {
    rwnotify:log-event-id 00040041;
    description "Uncorrelated block result";
    uses rwlog:severity-error;

    uses dtsrouter-xact-attr;

    leaf log {
      description "Log message";
      type string;
    }
    leaf hasblock-id {
      description "has block id";
      type uint32;
    }
    leaf block-id {
      description "block id";
      type uint32;
    }
  }

  notification uncorrelated-empty-xact-result {
    rwnotify:log-event-id 00040042;
    description "Uncorrelated empty transaction result";
    uses rwlog:severity-error;

    uses dtsrouter-xact-attr;

    leaf log {
      description "Log message";
      type string;
    }
  }

  notification xact-send-prepare {
    rwnotify:log-event-id 00040043;
    description "Sending prepare statement";
    uses rwlog:severity-debug;
    uses dtsrouter-xact-attr;

    leaf log {
      description "Log message";
      type string;
    }

    uses dtsrouter-member-xact-attr;

    leaf block-idx {
      description "block idx";
      type uint32;
    }

    leaf req-queryidx {
      description "req query idx";
      type uint32;
    }
  }


  notification xact-send-msg {
    rwnotify:log-event-id 00040044;
    description "sending precommit/commit/abort messages";
    uses rwlog:severity-debug;

    uses dtsrouter-xact-attr;

    leaf log {
      description "Log message";
      type string;
    }

    uses dtsrouter-member-xact-attr;

  }

  notification xact-added-member {
    rwnotify:log-event-id 00040045;
    description "Added member";
    uses rwlog:severity-debug;

    uses dtsrouter-xact-attr;

    leaf log {
      description "Log message";
      type string;
    }


    leaf member-name {
      description "member name";
      type string;
    }
    leaf req-idx {
      description "request idx";
      type uint32;
    }
  }

  notification xact-error {
    rwnotify:log-event-id 00040046;
    description "General xact related error";
    uses rwlog:severity-error;
    uses dtsrouter-xact-attr;
    leaf log {
      description "Log message";
      type string;
    }
  }

  notification xact-info {
    rwnotify:log-event-id 00040047;
    description "General xact related info";
    uses rwlog:severity-info;

    uses dtsrouter-xact-attr;

    leaf log {
      description "Log message";
      type string;
    }
  }

  notification xact-debug {
    rwnotify:log-event-id 00040048;
    description "General xact related debug";
    uses rwlog:severity-debug;

    uses dtsrouter-xact-attr;

    leaf log {
      description "Log message";
      type string;
    }
  }

  notification xact-summary {
    rwnotify:log-event-id 00040049;
    description "xact summary";
    uses rwlog:severity-debug;

    uses dtsrouter-xact-attr;

    leaf log {
      description "Log message";
      type string;
    }
    uses dtsrouter-member-xact-attr;

    leaf req-done {
      type uint32;
    }
    leaf req-ct {
      type uint32;
    }
    leaf block-idx {
      type uint32;
    }
    leaf n_query {
      type uint32;
    }
    leaf destset_ct {
      type uint32;
    }
  }
  notification xact-not-found {
    rwnotify:log-event-id 00040050;
    description "xact not found";
    uses rwlog:severity-error;

    uses dtsrouter-xact-attr;

    leaf log {
      description "Log message";
      type string;
    }
  }

  notification xact-filtered-member {
    rwnotify:log-event-id 00040045;
    description "Filtered member";
    uses rwlog:severity-debug;

    uses dtsrouter-xact-attr;

    leaf log {
      description "Log message";
      type string;
    }


    leaf member-name {
      description "member name";
      type string;
    }
    leaf req-idx {
      description "request idx";
      type uint32;
    }
  }

  notification received-member-reg {
    rwnotify:log-event-id 00040046;
    description "Router received a member registration request";
    uses rwlog:severity-info;
    leaf log {
      type string;
    }
    uses dtsrouter-reg-attr;

    leaf num-reg {
      description "Number of keyspecs in registration req";
      type uint32;
    }
  }

  notification non-owner-xact-end-attempt {
    rwnotify:log-event-id 00040051;
    description "Non owner trying to end the xact";
    uses rwlog:severity-error;

    uses dtsrouter-xact-attr;

    leaf log {
      description "Log message";
      type string;
    }
  }

  notification illegal-block-addition {
    rwnotify:log-event-id 00040052;
    description "Illegal block addition";
    uses rwlog:severity-error;

    uses dtsrouter-xact-attr;

    leaf log {
      description "Log message";
      type string;
    }
  }

  notification peer-reg-failure {
    rwnotify:log-event-id 00040053;
    description "Peer Reg failure";
    uses rwlog:severity-info;
    uses dtsrouter-gen-attr;

    leaf log {
      type string;
    }

    leaf peer {
      type string;
    }

    leaf retry {
      type uint32;
    }
  }

  notification abort-stop-from-member {
    rwnotify:log-event-id 00040054;
    description "Abort Stop From Member";
    uses rwlog:severity-error;
    uses dtsrouter-gen-attr;

    leaf log {
      type string;
    }
  }

  notification xact-dump-timeout {
    rwnotify:log-event-id 00040055;
    description "xact timer timeout dump";
    uses rwlog:severity-error;
    uses dtsrouter-gen-attr;

    leaf log {
      type string;
    }
    leaf xact-id {
      type string;
    }
    
  }

  notification dtsrouter-xact-debug {
    rwnotify:log-event-id 00040000;
    description "DTS Router xact debug log";
    uses rwlog:severity-debug;
    leaf log {
      type string;
    }
    uses dtsrouter-xact-attr;
  }

  /*
   * Log Keyspec error
   */
  notification notify-keyspec-error {
    rwnotify:log-event-id 00030068;
    description "DTS Keyspec error";
    uses rwlog:severity-error;
    leaf keyspec-error-string {
      description "log message";
      type string;
    }
  }

  /*
   * Log errors generated during a transaction
   */
  notification notify-xact-query-error {
    rwnotify:log-event-id 00030069;
    description "DTS xact query error";
    uses rwlog:severity-error;
    leaf query-keyspec {
      description "Keyspec in query";
      type string;
    }
    leaf error-cause {
      description "Error reason";
      type uint32;
    }
    leaf error-string {
      description "Error string";
      type string;
    }
    leaf corrid {
      description "Query corrid";
      type uint64;
    }
    leaf query-index {
      description "Query index";
      type uint32;
    }
    leaf serial-num {
      description "Query serial number";
      type uint64;
    }
    leaf client-idx {
      description "Clinet index";
      type uint64;
    }
    leaf router-idx {
      description "Router index";
      type uint64;
    }
    leaf block-idx {
      description "Block index";
      type uint32;
    }
    leaf client-path {
      description "Client path";
      type string;
    }
    leaf router-path {
      description "Router path";
      type string;
    }
    leaf tasklet-name {
      description "Tasklet name";
      type string;
    }
    leaf tasklet-instance {
      description "Tasklet instance";
      type uint32;
    }
    leaf query-action {
      description "Query action";
      type uint32;
    }
    leaf query-flags {
      description "Query flags";
      type uint32;
    }
  }
} // module rw-dts-router-log
