/*
 * 
 * (c) Copyright RIFT.io, 2013-2016, All Rights Reserved
 *
 *
 */

module rw-dts-tailf
{
  namespace "http://riftio.com/ns/riftware-1.0/rw-dts-tailf";
  prefix "rw-dts-tailf";

  import rw-dts {
    prefix rwdts;
  }

  import tailf-common {
    prefix tailf;
  }

  tailf:annotate "/rwdts:dts/rwdts:member" {
    tailf:callpoint base_show;
  }

  tailf:annotate "/rwdts:dts/rwdts:routers" {
    tailf:callpoint base_show;
  }
  
  tailf:annotate "/rwdts:rtr-init-reg-id" {
    tailf:callpoint base_show;
  }

  tailf:annotate "/rwdts:rtr-init-reg-keyspec" {
    tailf:callpoint base_show;
  }

  tailf:annotate "/rwdts:rtr-peer-reg-keyspec" {
    tailf:callpoint base_show;
  }

  tailf:annotate "/rwdts:member-info-bcast" {
    tailf:callpoint base_show;
  }
  
  tailf:annotate "/rwdts:start-dts" {
    tailf:actionpoint rw_action;
  }

  tailf:annotate "/rwdts:stop-dts" {
    tailf:actionpoint rw_action;
  }

}
