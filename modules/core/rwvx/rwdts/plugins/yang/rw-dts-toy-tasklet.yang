/*
 * 
 * (c) Copyright RIFT.io, 2013-2016, All Rights Reserved
 *
 *
 */

module rw-dts-toy-tasklet
{
  namespace "http://riftio.com/ns/riftware-1.0/rwdtstoytasklet";
  prefix "rw-dts-toy-tasklet";

  import rw-pb-ext {
    prefix "rwpb";
  }

  import rw-yang-types {
    prefix rwt;
  }

  import rw-cli-ext {
    prefix "rwcli";
  }

  import rw-log {
    prefix "rwlog";
  }

  import rw-notify-ext {
    prefix "rwnotify";
  }

  revision 2015-04-07 {
    description
      "Initial revision.  The yang file for DTS  Python Toy tasklet";
    reference
      "Used rw-base as a templagte";
  }

  /*
    +-- Containers for the DTS toy tasklet
  */

  container a-container {
    rwpb:msg-new AContainer;
    leaf an-int {
      type int32;
    }
    leaf a-boolean {
      type boolean;
    }
    leaf a-string {
      type string;
    }
  }

  container another-container {
    rwpb:msg-new AnotherContainer;
    leaf val {
      type string;
    }
  }

  /*
    +-- A container for the DTS toy tasklet
  */
  container a-flat-container {
    /* rwpb:msg-new AFlatContainer;*/
    rwpb:msg-flat true;
    leaf an-int {
      type int32;
    }
    leaf a-boolean {
      type boolean;
    }
    leaf a-string {
      rwpb:field-string-max 128;
      type string;
    }
  }

  /*
    +-- A list example
  */
  list employee {
    rwpb:msg-new Employee;
    key "name";
    leaf name {
      rwpb:field-inline "true";
      rwpb:field-string-max 64;            
      type string {
        length "1..256";
      }
    }
    leaf age {
      type uint32;
    }
    leaf ssn {
      rwpb:field-inline "true";
      rwpb:field-string-max 64;            
      type string {
        length "1..64";
      } 
    }
    leaf phone {
      rwpb:field-inline "true";
      rwpb:field-string-max 64;
      type string {
        length "1..20";
      }
    }
  }

  typedef industry-type {
    description "Inudtry type";
    type enumeration {
      enum basic-materials;
      enum conglomerates;
      enum consumer-goods;
      enum financial;
      enum health-care;
      enum indutrial-goods;
      enum services;
      enum technology;
      enum utilities;
      enum agriculture;
      enum energy;
    }
  }

  list company {
    key "name";
    rwpb:msg-new Company;
    description "A company";

    config false;
    leaf name {
      type string;
    }

    container profile {
      leaf industry {
        type industry-type;
      }
      leaf revenue {
        type string;
      }
      list office-locations {
        key "location-code";
        leaf location-code {
          description "Office location code";
          type int32;
        }
        leaf location-name {
          description "Name of the office location";
          type string;
        }
        
        container contact-info {
          description "Contact Information";
          leaf name {
            description "Name of the company";
            type string;
          }   
          leaf address {
            description "Address of the company";
            type string;
          }   
          leaf phone-number {
            description "company Phone Number";
            type string;
          }   
        }
        list printer-details {
          description "Printer Details at the location";
          key "identifier";
          leaf identifier {
            description "Id of the printer";
            type string;
          }
          leaf manufacturer {
            description "Manufacturer name";
            type string;
          }
        }
      }
    }


    grouping employee-details {
      leaf id {
        rwpb:field-inline "true";
        description "Employee Id";
        type int32;
      }
      leaf name {
        description "Employee Name";
        type string;
      }   
      leaf title {
        description "Employee title";
        type string;
      }   
    }

    list management-team {
      key "id";
      uses employee-details;
    }

    list employee {
      description "Employee record";
      key "id";
      uses employee-details;
      leaf start-date {
        description "Employee start date";
        type string;
      }   
    }

    list product {
      description "Products";
      max-elements 16;
      //rwpb:field-inline "true";
      //rwpb:msg-flat "true";
      key "id";
 
      leaf id {
        description "Product Id";
        type int32;
      }   
      leaf name {
        description "Product Name";
        type string;
      }   
      leaf msrp {
        description "Product msrp";
        type string;
      }   
    }
    container board {
      description "board";
      list member {
        key "name";
        leaf name {
          type string;
        }
        leaf details {
          type string;
        }
      }
    }
  }

  container toytasklet-config {
    list company {
      key "name";
      rwpb:msg-new CompanyConfig;
      description "A company";

      config true;
      leaf name {
        type string;
      }
      leaf description {
        type string;
      }

      list property {
        key "name";
        description "Company property";
        leaf name {
          type string;
        }
        leaf value {
          type string;
        }
      }
    }
  }

  container toytasklet-colony {
    list colony {
      key "name";
      rwpb:msg-new ColonyConfig;
      description "A colony";

      config true;
      leaf name {
        type string;
      }
      
      list network-context {
        key "name";
        rwpb:msg-new NetworkContext;
        description "A NC";
       
        leaf name {
         type string;
        }

        container nc-data {
          leaf nc-info {
            type string;
          }
        }

        list interface {
          key "name";
          rwpb:msg-new Interface;
          description "A interface";

          leaf name {
            type string;
          }

          leaf inter-info {
            type string;
          }
        }
      }
    }
  }

  container stats-data {
    rwpb:msg-new StatsData;
    leaf stats1 {
      type uint64;
    }
    leaf stats2 {
      type uint64;
    }
    leaf stats3 {
      type uint64;
    }
    leaf payload {
      type string;
    }
    leaf srcip {
      type rwt:ip-address;
      rwpb:field-c-type "rw_ip_addr_t";
      rwpb:field-string-max 46;
    }
  }

  rpc toy-rpc {
    input {
      rwpb:msg-new "ToyRpcInput";
      leaf val {
        description "Input value";
        type string;
      }
    }

    output {
      rwpb:msg-new "ToyRpcOutput";
      leaf ret {
        description "Return value";
        type string;
      }
    }
  }

  notification event-route-added {
    description "Notification for new route";
    leaf name {
      description "Route name";
      type string;
    }

    leaf id {
      description "Route ID";
      type uint16;
    }
  }
}
