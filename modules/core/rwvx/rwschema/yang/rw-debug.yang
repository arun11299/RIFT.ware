/*
 * 
 * (c) Copyright RIFT.io, 2013-2016, All Rights Reserved
 *
 *
 */

module rw-debug
{
  namespace "http://riftio.com/ns/riftware-1.0/rw-debug";
  prefix "rw-debug";

  import rw-pb-ext {
    prefix "rwpb";
  }

  import rw-yang-types {
    prefix rwt;
  }

  import rw-cli-ext {
    prefix "rwcli";
  }

  import rw-log {
    prefix "rwlog";
  }

  import rw-notify-ext {
    prefix "rwnotify";
  }

  revision 2014-05-29 {
    description
      "Initial revision. This YANG file defines common groupings, typedefs, and
       containers available on Riftware";
    reference
      "Derived from earlier versions of debug YANG files";
  }

  container rw-debug {
    description "Tasklet related information";

    container resource {
      config false;
      description "Provdides tasklet resource usage information";

      list tasklet {
        key "name";

        leaf name {
          description "";
          type string;
        }

        container memory {
          description "memory related information";
          leaf allocated {
            description "Amount of memory allocated";
            type uint64;
          }
          leaf chunks {
            description "Number of memory chunks allocated";
            type uint64;
          }
        }

        container scheduler {
          description "Scheduler Related Counters and States";
          container counters {
            description "Various Scheduler Counters";
            leaf sources {
              description "Number of Sources";
              type uint32;
            }
            leaf queues {
              description "Number of Queues";
              type uint32;
            }
            leaf sthread_queues {
              description "Number of Static Thread Queues";
              type uint32;
            }
            leaf sockets {
              description "Number of Sockets";
              type uint32;
            }
            leaf socket_sources {
              description "Number of Socket Sources";
              type uint32;
            }
          }
        }
      }
    }

    container heap {
      config false;
      description "Provdides the tasklet's memory-heap usage information";

      list tasklet {
        key "name";
        rwpb:field-merge-behavior none;

        leaf name {
          description "";
          type string;
        }

        list allocation {
          //COMMENTED key "address";
          //COMMENTED rwpb:field-merge-behavior none;

          leaf address {
            description "memory address of the allocation";
            type uint64;
          }
          leaf type {
            description "type of the allocation";
            type string;
          }
          leaf size {
            description "size of the allocation";
            type uint32;
          }
          list caller {
            leaf info {
              description "caller stack for the allocation";
              type string;
            }
          }
        }

        container memory {
          description "memory related information";
          leaf allocated {
            description "Amount of memory allocated";
            type uint64;
          }
          leaf chunks {
            description "Number of memory chunks allocated";
            type uint64;
          }
        }
      }
    }

    container settings {
      container heap {
        description "Tasklet heap related configuration";
        leaf depth {
          description "Depth of the call stack to be captured";
          type uint32 {
            range "1..100";
          }
        }
      }
      container scheduler {
        description "Tasklet scheduler configuration";
        leaf latency-threshold {
          description "Milliseconds after which to report long running event callbacks or zero to disable";
          type uint32 {
            range "0..10000";
          }
        }
      }
    }
  }
}
