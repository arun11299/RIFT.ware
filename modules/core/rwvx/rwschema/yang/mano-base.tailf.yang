/*
 * 
 * (c) Copyright RIFT.io, 2013-2016, All Rights Reserved
 *
 *
 */

module mano-base.tailf
{
    namespace "http://riftio.com/ns/riftware-1.0/mano-base-annotation";
    prefix "mano-base-ann";
    
    import mano-base {
        prefix manobase;
    }
    import tailf-common {
        prefix tailf;
    }

    tailf:annotate "/manobase:vnf-opdata/manobase:vnf" {
      tailf:callpoint base_show;
    }
}
