/*
 * 
 * (c) Copyright RIFT.io, 2013-2016, All Rights Reserved
 *
 *
 */

module rw-dtsperf-annotation
{
  namespace "http://riftio.com/ns/riftware-1.0/rw-dtsperf-annotation";
  prefix "rw-dtsperf-ann";

  import tailf-common {
    prefix tailf;
  }

  import rw-base {
    prefix rwbase;
  }


  import rw-dtsperf {
    prefix rwdtsperf;
  }

  tailf:annotate "/rwdtsperf:perf-statistics" {
    tailf:callpoint base_show;
  }
  tailf:annotate "/rwdtsperf:start-xact" {
    tailf:actionpoint rw_action;
  }
}
