/*
 * 
 * (c) Copyright RIFT.io, 2013-2016, All Rights Reserved
 *
 *
 */

// Configuration references

module rw-dtsperf
{
  namespace "http://riftio.com/ns/riftware-1.0/rw-dtsperf";
  prefix "rwdtsperf";

  import rw-pb-ext { prefix "rwpb"; } 
  import rw-cli-ext { prefix "rwcli"; }

  description "DTS performance yang";
  revision 2014-05-11 {
    description "Initial version"; 
  }

  typedef resp-invoke-xact {
    type enumeration {
      enum sub-xact;
      enum new-xact;
    }
  }

  typedef resp-character {
    type enumeration {
      enum delay-rsp;
      enum async-and-rsp;
      enum invoke-xact-rsp;
    }
  }

  typedef resp-type {
    type enumeration {
      enum ack;
      enum nack;
      enum not-applicable;
    }
  }

  typedef xact-oper {
    type enumeration {
      enum create;
      enum read;
      enum update;
    }
  }

  typedef xact-mode {
    type enumeration {
      enum transactional;
      enum nontransactional;
    }
  }

  typedef in-xact-repeat-mode {
    type enumeration {
      enum wait_finish_and_repeat;
      enum periodic_repeat;
    }
  }
  grouping xact-stats {
    leaf tot-xacts {
      type uint32;
      description "Number of transactions";
    }
    leaf tot-xacts-from-rsp {
      type uint32;
      description "Xacts as sub xact";
    }
    leaf tot-subq-from-rsp {
      type uint32;
      description "Xacts as sub query";
    }
    leaf tot-rsps {
      type uint32;
      description "Number of response callbacks";
    }
    leaf send-rsps {
      type uint32;
      description "Number of response sent";
    }
    leaf succ-count {
      type uint32;
      description "successful count";
    }
    leaf fail-count {
      type uint32;
      description "failed/no result count";
    }
    leaf abrt-count {
      type uint32;
      description "Aborted count";
    }
    leaf curr-outstanding {
      type uint32;
      description "Current outstanding xacts";
    }
    leaf curr-xact-count {
      type uint32;
      description "Current xact count in this iteration";
    }
    leaf rtt-less-2-exp-0 {
      type uint32;
      description "RTT less than 2 exp 0";
    }
    leaf rtt-less-2-exp-1 {
      type uint32;
      description "RTT less than 2 exp 1";
    }
    leaf rtt-less-2-exp-2 {
      type uint32;
      description "RTT less than 2 exp 2";
    }
    leaf rtt-less-2-exp-3 {
      type uint32;
      description "RTT less than 2 exp 3";
    }
    leaf rtt-less-2-exp-4 {
      type uint32;
      description "RTT less than 2 exp 4";
    }
    leaf rtt-less-2-exp-5 {
      type uint32;
      description "RTT less than 2 exp 5";
    }
    leaf rtt-less-2-exp-6 {
      type uint32;
      description "RTT less than 2 exp 6";
    }
    leaf rtt-less-2-exp-7 {
      type uint32;
      description "RTT less than 2 exp 7";
    }
    leaf rtt-less-2-exp-8 {
      type uint32;
      description "RTT less than 2 exp 8";
    }
    leaf rtt-less-2-exp-9 {
      type uint32;
      description "RTT less than 2 exp 9";
    }
    leaf rtt-less-2-exp-10 {
      type uint32;
      description "RTT less than 2 exp 10";
    }
    leaf rtt-less-2-exp-11 {
      type uint32;
      description "RTT less than 2 exp 11";
    }
    leaf rtt-less-2-exp-12 {
      type uint32;
      description "RTT less than 2 exp 12";
    }
    leaf rtt-less-2-exp-13 {
      type uint32;
      description "RTT less than 2 exp 13";
    }
    leaf rtt-less-2-exp-14 {
      type uint32;
      description "RTT less than 2 exp 14";
    }
    leaf rtt-less-2-exp-15 {
      type uint32;
      description "RTT less than 2 exp 15";
    }
    leaf rtt-greater {
      type uint32;
      description "RTT greater than 2 exp 15";
    }
    list latency-averages {
      key xact-name;
      leaf xact-name {
        type string;
        rwpb:field-string-max "32";
        mandatory true;
        description "Transaction name";
      }
      leaf num-xacts {
        type uint32;
        description "Number of transactions in the average calc";
      }
      leaf ave-latency {
        type uint64;
        description "Average transaction time in usec";
      }
      leaf min-latency {
        type uint64;
        description "Minimum latency in usec";
      }
      leaf max-latency {
        type uint64;
        description "Maximum latency in usec";
      }
      leaf variance {
        type uint64;
        description "Variance of latency in usec";
      }
    }
  }

  grouping publish-data {
    list list-data {
      key any-data;
      leaf any-data {
        type string;
        rwpb:field-string-max "64";
      }
      leaf more-listy-data {
        type string;
        rwpb:field-string-max "1024";
      }
    }
  }

  grouping xact-repeat {
    container xact-repeat {
      description "xact repeat pattern";
      choice repeat-pattern {
        case run-till-end {
          description "run the xacts sequentially";
          container run-till-end {
            leaf sequential {
              type boolean;
              description "xact execution";
            }
          }
        }
        case delay-and-repeat {
          description "invoke xacts based on a timer";
          container delay-and-repeat {
            leaf delay-between-xacts {
              type uint32; 
              description "delay timer between xacts";
            }
          }
        }
        case outstanding-and-repeat {
          description "ensure outstanding xacts till max xacts invoked";
          container outstanding-and-repeat {
            leaf num-xact-outstanding {
              type uint32;
              description "outstanding xacts at any time";
            }
            leaf xact-max-with-outstanding {
              type uint32;
              description "max num od xacts";
            }
          }
        }
      }
    }
  }
  grouping task-config {
    rwcli:new-mode "task-config";
    container subscriber-config {
      description "DTSPerf tasklet subscriber config";
      rwcli:new-mode "subsc-config";
      list rsp-flavor {
        key rsp-flavor-name;
        leaf rsp-flavor-name {
          type string; 
          rwpb:field-string-max "32"; 
          mandatory true;
          description "Response flavor name";
        }
        rwcli:new-mode "rsp-flavor";
        leaf next-xact-name {
          type string;
          rwpb:field-string-max "32"; 
          description "Set xact-name for subsequent transaction";
        }
        leaf rsp-character {
          type resp-character;
          description "Response Immediate/Delay,Async and Respond OR Invoke Xact and Respond";
        }
        leaf rsp-invoke-xact {
          type resp-invoke-xact;
          description "Invoke Xact as subquery or new xact";
        }
        leaf num-rsp {
          type uint32;
          description "Number of responses";
        }
        leaf rsp-delay-interval {
          type uint32;
          description "Delay between responses in ms";
        }
        leaf payload-len {
          type uint32;
          description "Length of payload in each response";
        }
        leaf payload-pattern {
          type string;
          rwpb:field-string-max "32"; 
          description "Any payload pattern";
        }
        leaf rsp-type {
          type resp-type;
          description "Response type ACK/NACK/NA";
        }
        leaf rsp-cache {
          type boolean;
          description "use CACHE_FLAG for this rsp behavior";
        }
      }
      list subsc-instance-id {
        key instance-id;
        leaf instance-id {
          type int32;
          mandatory true;
          description "subscribe instance id number";
        }
      }
    }
    container xact-config {
      description "DTSPerf tasklet transaction config";
      rwcli:new-mode "xact-config";
      list xact {
        key xact-name;
        leaf xact-name {
          type string;
          rwpb:field-string-max "32";
          mandatory true;
          description "Transaction name";
        }
        rwcli:new-mode "xact-detail";
        container xact-detail {
          leaf xact-operation {
            type xact-oper;
            description "Transaction for Config!/Read/Write";
          }
          leaf xact-type {
            type xact-mode;
            description "Transaction Blocking/Nonblocking";
          }
          leaf xact-stream-flag {
            type boolean;
            description "stream flag state while creating xact";
          }
          leaf xact-blockmerge-flag {
            type boolean;
            description "flag state while creating xact";
          }
          leaf in-xact-repeat-count {
            type uint32;
            description "Repeat of messages within same transaction";
          }
          leaf in-xact-repeat-delay {
            type uint32;
            description "Delay in repeat of messages within same transaction";
          }
          leaf in-xact-repeat-character {
            type in-xact-repeat-mode;
            description "Determine how to Repeat of messages within same transaction";
          }
          leaf xact-repeat-count {
            type uint32;
            description "Repeat count for this transaction";
          }
          leaf xact-delay-interval {
            type uint32;
            description "Delay between invoking Transactions in ms";
          }
          leaf xact-rsp-flavor {
            type string;
            rwpb:field-string-max "32";
            mandatory true;
            description "rsp-flavor for this transaction";
          }
          leaf payload-len {
            type uint32;
            description "Length of payload";
          }
          leaf payload-pattern {
            type string;
            rwpb:field-string-max "32";
            description "Any payload pattern";
          }
        }
      }
      uses xact-repeat;
    }
  }

  list perf-statistics {
    config false;
    rwpb:msg-new "PerfStatistics";
    key instance-id;
    leaf instance-id {
       type int32;
    }
    leaf start-tv-sec {
       type int64;
    }
    leaf start-tv-usec {
       type int64;
    }
    leaf end-tv-sec {
       type int64;
    }
    leaf end-tv-usec {
       type int64;
    }
    uses xact-stats;
  }

  container perfdts-config {
    description "Configuring DTSPerf tasklets";
    rwcli:new-mode "perfdts-config";
    rwpb:msg-new "PerfdtsConfig";
    container config-all {
      uses task-config;
    }
    container config-task-instance {
      list instance-id {
        key instance;
        leaf instance {
          type int32;
          description "xpath instance id";
        }
        leaf task-instance-id {
          type int32;
          mandatory true;
          description "tasklet instance id";
        }
        rwcli:new-mode "instance-id-config";
        container instance-config {
          uses task-config;
        }
      }
    }
  } 
  
  container xact-msg {
    rwpb:msg-new XactMsg;
    list content {
      key xact-detail;
      leaf xact-detail {
        type string;
        rwpb:field-string-max "32";
        description "rsp-flavor for this transactions";
      }
      leaf input-payload {
        type string;
        description "payload string";
      }
    }
  }

  rpc start-xact {
    input {
      rwpb:msg-new StartXact;
      rwpb:msg-flat true;
      leaf instance-id {
        type uint32;
        description "DTSPerf task instance id";
      }
    }
    output {
      leaf instance-id {
        type uint32;
        description "DTSPerf task instance id";
      }
    }
  } // rpc start-xact
} // module rw-dtsperf
