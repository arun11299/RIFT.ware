/*
 * 
 * (c) Copyright RIFT.io, 2013-2016, All Rights Reserved
 *
 *
 */

module rw-memlog.tailf
{
  namespace "http://riftio.com/ns/riftware-1.0/rw-memlog.tailf";
  prefix "rw-memlog-ann";

  import tailf-common {
    prefix tailf;
  }

  import rw-memlog {
    prefix rw-memlog;
  }

  tailf:annotate "/rw-memlog:rw-memlog-state" {
    tailf:callpoint base_show;
  }

  tailf:annotate "/rw-memlog:rw-memlog-command" {
    tailf:actionpoint rw_action;
  }
}
