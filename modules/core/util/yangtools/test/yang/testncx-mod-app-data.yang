/*
 * 
 * (c) Copyright RIFT.io, 2013-2016, All Rights Reserved
 *
 */



/**
 * @file testncx-mod-app-data-app-data.yang
 * @author Rajesh Velandy
 * @date 2014/07/2014
 * @brief Test application data extensions
 */

module testncx-mod-app-data
{
  namespace "http://riftio.com/ns/core/util/yangtools/tests/testncx-app-data";
  prefix "tmnad";

  import rw-utcli-ext { prefix "rwutcli"; }
  import rw-pb-ext { prefix "rwpb"; }

  description "Test application data extensions.";
  revision 2014-06-03 { description "Initial version"; }

  extension mext1 {
    argument "foo";
    description "ext1 extension";
  }

  extension mext2 {
    argument "foo";
    description "ext1 extension";
  }

  tmnad:mext1 "ext1 in module";

  tmnad:mext2 "ext2 in module";


  container top {
    tmnad:mext1 "ext1 in top";
    container a {
      tmnad:mext1 "ext1 in a";

      container a-1 {
        tmnad:mext1 "ext1 in a-1";
      }

      container a-2 {
        leaf junk { type string; }
      }

      leaf n1 {config true; type int8 {range "-12..14";} }
      leaf n2 { type int16 {range "100..200|300|400..500";} config true; }
      leaf n3 { type int32; config false; }
      leaf n4 { type int64; config false; }
      leaf n5 { type uint8; config true; }
      leaf n6 { type uint16; config true; }
      leaf n7 { type uint32; config false; }
      leaf n8 { type uint64; config false; }
    }

    container b {
      rwpb:msg-new TmnadContainerB;
      rwutcli:callback-argv "tmnad_app_data_callback_b";
      tmnad:mext2 "ext2 in b";
      tmnad:mext2 "ext2 in b";

      container b-1 {
        tmnad:mext1 "ext1 in b-1";
      }

      container b-2 {
        leaf junk { type string; }
      }

      leaf bin1 { type binary {length "2..5";}}
      leaf bool1 { type boolean; }
      leaf dec1 { type decimal64 { fraction-digits 1; } }
      leaf e1 { type empty; }
      leaf s1 { type string{length "2..5";} }
    }
  }
}
