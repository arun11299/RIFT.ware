/*
 * 
 * (c) Copyright RIFT.io, 2013-2016, All Rights Reserved
 *
 *
 */

module rw-log-e
{
  namespace "http://riftio.com/ns/riftware-1.0/rw-log";
  prefix "rwlog";

  import rw-pb-ext {
    prefix "rwpb";
  }

  import rw-notify-ext {
    prefix "rwnotify";
  }

  import rw-yang-types {
    prefix "rwt";
  }

  revision 2014-05-29 {
    description
      "Initial revision. This YANG file defines common groupings, typedefs, and
       containers available on Riftware for logging";
    reference
      "Derived from earlier versions of base YANG files";
  }

  // gah, this becomes RW_LOG_LOG_SEVERITY_mumble
  typedef log-severity {
    type enumeration {
      enum emergency;
      enum alert;
      enum critical;
      enum error;
      enum warning;
      enum notice;
      enum info;
      enum debug;
    }
  }

  typedef direction_type {
    type enumeration {
      enum INBOUND {value 1;}
      enum OUTBOUND {value 2;}
    }
  }

  typedef protocol_type {
    type enumeration {
      enum IP;
      enum TCP;
      enum UDP;
      enum ETHERNET;
      enum GTP;
    }
  }

  typedef on_off_type {
    type enumeration {
      enum off;
      enum on;
    }
  }

  grouping packet-info {
    container pkt-info {
    rwpb:field-inline "true";
    description "Different protocol prints need different arguments. This
        container holds all the fields needed by various protocol print
        functions";
      leaf packet-direction {
        description "Either inbound or outbound direction";
        type direction_type;
      }
      leaf packet-type {
        description "Packet protocol type";
        type protocol_type;
      }
      leaf packet-data {
        description "Packet data";
        type binary;
      }
      leaf sport {
        description "Source port needed for GTP print";
        type uint16;
      }
      leaf dport {
        description "Destination port for GTP print";
        type uint16;
      }
      leaf ip-header {
        description "IP header pointer needed for TCP/UDP prints";
        type uint64;
      }
      leaf fragment {
        description "Whether packet is fragmented or not. Needed for tcp and udp
            prints";
        type uint32;
      }
    }
  }

  typedef pointer {
    description "A pointer is an often logged object. This generic type allows
                 for pointers to be displayed differently by netconf clients";
    type uint64;
  }
  
// Event Log ID namespace Conventions:
// Leaving adequate gaps for expansion or allocation to newer apps
// rw-log           : 00000000 - 00000099 
// rw-fpath         : 00001000 - 00001999 
// rw-vcs           : 00010000 - 00010999 
// rw-appmgr        : 00020000 - 00020999
// rw-dts-api       : 00030000 - 00030999
// rw-dts-rtr       : 00040000 - 00040999
// rwvm-heartbeat   : 00050000 - 00050999
// rw-logger        : 00060000 - 00060099
// rw-netns-log     : 00061000 - 00061099
// rw-mgmt*         : 00070000 - 00079999
// rw-mgmtagent     : 00080000 - 00089999
// rw-ncmgr-log     : 00090000 - 00099999
// rw-ifmgr-log     : 00100000 - 00109999

/* Ensure category name dont overlap like  rv-vcs and rw-vcs-log 
   since otherwise show-logs doesnt recognize the category. See JIRA 4167 
   Add Event Log ID range comment above when you add a new category */

  typedef log-category {
    type enumeration {
      enum all;
      enum rw-fpath-log;
      enum rw-vcs;
      enum rw-appmgr-log;
      enum rw-dts-api-log;
      enum rw-dts-router-log;
      enum rw-logtest;
      enum rw-logger;
      enum rw-vm-heartbeat-log;
      enum rw-netns-log;
      enum rw-mgmtagt-log;
      enum rw-ncmgr-log;
      enum rw-ifmgr-log;
    }
  }

  grouping session-grp-params {
    container session-params {
      description "Session parametes";
      leaf imsi {
        description "IMSI for the session";
        rwpb:field-inline "true";
        rwpb:field-string-max 16;
        type string;
      }
      leaf ip-address {
        description "IP Address for the session";
        rwpb:field-inline "true";
        rwpb:field-string-max 64;
        type rwt:ip-address;
      }
    }
  }

  grouping common-attrs  {
    leaf event-id  {
      rwpb:field-inline "true";
      type uint32;
      rwnotify:log-common;
    }
    leaf version  {
      rwpb:field-inline "true";
      type uint32;
      rwnotify:log-common;
    }
    leaf sequence {
      rwpb:field-inline "true";
      type uint64;
      rwnotify:log-common;
    }
    leaf sec {
      rwpb:field-inline "true";
      type uint32;
      rwnotify:log-common;
    }
    leaf usec {
      rwpb:field-inline "true";
      type uint32;
      rwnotify:log-common;
    }
    leaf system-id{
      rwpb:field-inline "true";
      type uint32;
      rwnotify:log-common;
    }
    leaf hostname {
      type string;
      rwnotify:log-common;
      rwpb:field-inline "true";
      rwpb:field-string-max "64";
    }
    leaf appname {
      type string; 
      rwnotify:log-common;
      rwpb:field-inline "true";
      rwpb:field-string-max "64";
    }
    leaf processid{
      rwpb:field-inline "true";
      type uint32;
      rwnotify:log-common;
    }
    leaf threadid{
      type uint32;
      rwnotify:log-common;
    }
    leaf filename {
      type string;
      rwnotify:log-common;
      rwpb:field-inline "true";
      rwpb:field-string-max "64";
    }
    leaf linenumber{
      rwpb:field-inline "true";
      type uint32;
      rwnotify:log-common;
    }
    leaf severity{
      rwpb:field-inline "true";
      type log-severity;
    }
    leaf call-arrived-time {
      description "Call arrived time";
      type uint32;
    }
    leaf call-failure {
      description "Call failure status";
      type boolean;
    }
    uses group-call-id;
    uses session-grp-params;
  }

  grouping invalidate-call-params {
      leaf invalidate_call-time {
        type rwt:date-and-time;
      }
  }

  grouping call-failure-params {
    leaf call-failure-cause {
      type string;
    }
  }

  grouping severity-emergency {
    container template_params {
      rwpb:field-inline "true";
      uses common-attrs {
        refine severity {default emergency;}
      }
    }
  }
  grouping severity-alert {
    container template_params {
      rwpb:field-inline "true";
      uses common-attrs {
        refine severity {default alert;}
      }
    }
  }
  grouping severity-critical {
    container template_params {
      rwpb:field-inline "true";
      uses common-attrs {
        refine severity {default critical;}
      }
    }
  }
  grouping severity-error {
    container template_params {
      rwpb:field-inline "true";
      uses common-attrs {
        refine severity {default error;}
      }
    }
  }
  grouping severity-warning {
    container template_params {
      rwpb:field-inline "true";
      uses common-attrs {
        refine severity {default warning;}
      }
    }
  }
  grouping severity-notice {
    container template_params {
      rwpb:field-inline "true";
      uses common-attrs {
        refine severity {default notice;}
      }
    }
  }
  grouping severity-info {
    container template_params {
      rwpb:field-inline "true";
      uses common-attrs {
        refine severity {default info;}
      }
    }
  }
  grouping severity-debug {
    container template_params {
      rwpb:field-inline "true";
      uses common-attrs {
        refine severity {default debug;}
      }
    }
  }

  grouping group-call-id {
    container call-identifier {
      rwpb:field-inline "true";
      description "Each call in Riftware is assigned a callid which is unique
                   in the context of the entity making the assignment. The
                   same call-id could be assigned by different entities - in
                   which case, the group-call-id is used in conjunction with
                   call id to provide uniqueness";
      leaf callid {
        description "The callid is defined as a grouping with a leaf that represents
                 the callid. This helps in RIFTWARE use a common tag for call-id
                 in all further uses of this grouping.";

        type uint64;
      }
      leaf groupcallid {
        description "The group call id is used to uniquely identify the assigner of
                 a call id. Each entity generating call id within RIFTWARE uses
                 group ids that are different from each other. A single entity
                 could use multiple group ids - The caveat being that none of
                 these group ids should be avaialble for other entities to use";
        type uint64;
      }
    }
  }

  grouping msg-id {
    leaf tv-sec  {
      description "seconds";
      type uint32;
    }
    leaf tv-usec {
      description "micro seconds";
      type uint32;
    }
    leaf hostname  {
      description "hostname";
      rwpb:field-inline "true";
      rwpb:field-string-max yang;
      type string {
        length "1..64";
      }
    }
    leaf process-id  {
      description "process id";
      type uint32;
    }
    leaf thread-id  {
      description "thread id";
      type uint32;
    }
    leaf seqno  {
      description "sequence no";
      type uint64;
    }
  }

  grouping attribute-filter {
    leaf name {
      description "Filter Attribute Name";
      rwpb:field-inline "true";
      rwpb:field-string-max yang;
      type string {
        length "1..64";
      }
    }
    leaf value {
      description "Filter Attribute Value";
      rwpb:field-inline "true";
      rwpb:field-string-max yang;
      type string {
        length "1..64";
      }
    }
  }

  grouping show-log-category-filter {

      leaf name {
        description "Log Category name";
        type log-category;
      }

      list attribute {
        description "attribute name, value pair for filter";
        key "name";
        uses attribute-filter;
      }

      leaf severity {
        description "level symbolic name";
        type log-severity;
      }
  }

  grouping show-logs-input {
    choice show-logs-choice {
      case show-logs-all {
      leaf all {
        type empty;
      }
      }
      case show-logs-rest {
      container filter {
        description "rwlog filter settings";
        list category {
          key "name";
          uses show-log-category-filter;
        }
        leaf callid {
         type uint64;
        }
        leaf groupcallid {
         type uint64;
        }
        uses session-grp-params;
        container binary-events {
          leaf packet-direction {
            description "Either inbound or outbound direction";
            type direction_type;
          }
          leaf protocol {
            description "Packet protocol type";
            type protocol_type;
          }
        }
      }
      container debug {
        description "Used for debugging";
        leaf suppress-display {
          type empty;
        }
        leaf dump-task-info {
          type int32;
          description "verbosity";
        }
        leaf filter-settings {
          description "show logging related severity levels";
          type empty;
        }
      }
      leaf severity {
        description "level symbolic name";
        type log-severity;
      }
      leaf start-time {
        type rwt:date-and-time;
      }
      leaf end-time {
        type rwt:date-and-time;
      }
      leaf verbosity {
          type int32 {
            range "0..5";
        }
        description "PDU Verbosity";
      }
      leaf count {
        type uint32 {
          range "1..10000";
        }
        description "Maximum number of Logs to be displayed. Default 100. Range
            1 to 10000";
      }
      leaf inactive {
        description "Fetch only checkpointed logs";
          type enumeration {
            enum events;
          }
      }
      leaf tail {
        description "Fetch the last logs";
        type empty;
          //type enumeration {
          //  enum events;
          //}
      }
      uses msg-id;
      }
    }
  }

  grouping show-logs-output {
      list logs{
        key "tv-sec tv-usec hostname process-id thread-id seqno";
        uses msg-id;
        leaf msg {
          type string;
          description "Log-String";
        }
        leaf pdu-detail {
          type string;
          description "PDU detail";
        }
        leaf pdu-hex {
          type string;
          description "PDU as hex";
        }
      }
      list log-summary {
        key "hostname";
        leaf hostname {
          type string;
          description "Sender's hostname";
          rwpb:field-inline "true";
          rwpb:field-string-max 64;
          //  MAX_HOSTNAME_SZ 64
        }
        leaf log-count {
          type uint32;
          description "Number of logs printed";
        }
        leaf time-spent {
          type int64;
          description "Time spent in fetching logs in msec";
        }
        leaf logs-muted {
          type uint64;
          description "Number of logs that did not match filter";
        }
        leaf tv-sec  {
          description "seconds";
          type uint32;
        }
        leaf tv-usec {
          description "micro seconds";
          type uint32;
        }
        leaf process-id  {
          description "process id";
          type uint32;
        }
        leaf thread-id  {
          description "thread id";
          type uint32;
        }
        leaf seqno  {
          description "sequence no";
          type uint64;
        }
        leaf trailing-timestamp {
          type string;
          description "Timestamp of last event considered";
        }
      }
      list severity-output {
        key "severity-info";
        leaf severity-info {
         description "category:severity information";
         type string;
        }
      }
  }

  notification ev_template {
    rwpb:msg-new EvTemplate;
      description
         "EventLog for pretty Print";
      uses severity-debug;
  }

  notification binary_event{
    rwpb:msg-new BinaryEvent;
      description
         "Packet info fields";
      uses packet-info;
  }

  rpc show-logs-internal {
    description "Fetches Log events";
    input {
      uses show-logs-input;
    }
    output {
      uses show-logs-output;
    }
  }

  list lead-rwlogd-data {
    config false;
    key "task-id";
    max-elements 1;
    leaf task-id {
      type uint32;
      description "Lead RwLogD Instance";
    }
  }

}
