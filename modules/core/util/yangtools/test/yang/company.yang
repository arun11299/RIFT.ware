/*
 * 
 * (c) Copyright RIFT.io, 2013-2016, All Rights Reserved
 *
 *
 */

module company
{
  namespace "http://riftio.com/ns/core/util/yangtools/tests/company";
  prefix "company";

  import rw-pb-ext { prefix "rwpb"; }
  description "This YANG module models a Company";

  revision 2014-05-27 {
    description "Initial version"; }

  rwpb:file-pbc-include "rwtypes.h";
  rwpb:file-pbc-include "rw_ip.h";
  rwpb:file-pbc-include "rw_sklist.h";

  container  company {
    rwpb:msg-new Company;
    description "A company";

    container contact-info {
      leaf name {
        description "Name of the company";
        type string;
      }
     
      leaf address {
        description "Address of the company";
        type string;
      }
      leaf phone-number {
        description "company Phone Number";
        type string;
      }
    }
    list employee {
      description "Employee record";
      key "id";

      leaf id {
        description "Employee Id";
        type int32;
      }
      leaf name {
        description "Employee Name";
        type string;
      }
      leaf title {
        description "Employee title";
        type string;
     }
     leaf start-date {
       description "Employee start date";
       type string;
     }

     container extra-curriculum {
       description "Employee extra curricular data";
       leaf interest {
        description "Special interests";
        type string;
       }
     }

  }

    
    list interests {
      description "Common employee interests";
      key "id domain name";

      leaf domain {
        type string;
      }

      leaf name {
        type string;
      }

      leaf id {
        type int32;
      }
    }


    list product {
      description "Products";
      key "id";
 
      leaf id {
        description "Product Id";
        type int32;
      }
      leaf name {
        description "Product Name";
        type string;
      }
      leaf msrp {
        description "Product msrp";
        type string;
      }
    }

    list department {
      key "id name";

      leaf level {
        type int32;
      }
      leaf id {
        type int32;
      }
      leaf name {
        type string;
      }
      leaf director {
        type string;
      }
    }
  }
}
