/*
 * 
 * (c) Copyright RIFT.io, 2013-2016, All Rights Reserved
 *
 *
 */

module lpmocklet-annotation
{
    namespace "http://riftio.com/ns/riftware-1.0/lpmocklet-annotation";
    prefix "lpmocklet-ann";

    import tailf-common {
        prefix tailf;
    }

    import lpmocklet {
        prefix lpmocklet;
    }

    tailf:annotate "/lpmocklet:lpmocklet-action-status" {
        tailf:callpoint base_show;
    }

    tailf:annotate "/lpmocklet:set-control-param" {
        tailf:actionpoint rw_action;
    }

    tailf:annotate "/lpmocklet:start-vnfr" {
        tailf:actionpoint rw_action;
    }

    tailf:annotate "/lpmocklet:stop-vnfr" {
        tailf:actionpoint rw_action;
    }
}
