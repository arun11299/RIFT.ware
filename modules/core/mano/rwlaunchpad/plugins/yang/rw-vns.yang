/*
 * 
 * (c) Copyright RIFT.io, 2013-2016, All Rights Reserved
 *
 */



/**
 * @file rw-vns.yang
 * @author Austin Cormier
 * @date 2015/10/06
 * @brief Virtual Network Service Yang
 */

module rw-vns
{
  namespace "http://riftio.com/ns/riftware-1.0/rw-vns";
  prefix "rw-vns";


  import rw-pb-ext {
    prefix "rwpb";
  }

  import rw-cli-ext {
    prefix "rwcli";
  }

  import rw-yang-types {
    prefix "rwt";
  }

  import rwcal {
    prefix "rwcal";
  }

  import rwsdn {
    prefix "rwsdn";
  }


  import ietf-yang-types {
    prefix "yang";
  }

  import rw-iwp {
    prefix "rwiwp";
  }

  import rw-vlr {
    prefix "rwvlr";
  }

  import vld {
    prefix "vld";
  }

  import ietf-network {
    prefix "nw";
  }

  import ietf-network-topology {
    prefix "nt";
  }

  import ietf-l2-topology {
    prefix "l2t";
  }

  import rw-topology {
    prefix "rw-topology";
  }

  import rw-resource-mgr {
    prefix "rw-resource-mgr";
  }

  import rw-sdn {
    prefix "rw-sdn";
  }

  revision 2015-10-05 {
    description
      "Initial revision.";
  }
}
