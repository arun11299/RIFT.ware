/*
 * 
 * (c) Copyright RIFT.io, 2013-2016, All Rights Reserved
 *
 *
 */

module vlr-annotation
{
  namespace "http://riftio.com/ns/riftware-1.0/vlr-annotation";
  prefix "vlr-ann";

  import tailf-common {
    prefix tailf;
  }

  import rw-base {
    prefix rwbase;
  }

  import vlr {
    prefix vlr;
  }
  tailf:annotate "/vlr:vlr-catalog" {
    tailf:callpoint base_show;
  }
}
