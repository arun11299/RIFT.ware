/*
 * 
 * (c) Copyright RIFT.io, 2013-2016, All Rights Reserved
 *
 *
 */

module rw-vnfd-annotation
{
  namespace "http://riftio.com/ns/riftware-1.0/rw-vnfd-annotation";
  prefix "rw-vnfd-ann";

  import tailf-common {
    prefix tailf;
  }

  import rw-base {
    prefix rwbase;
  }

  import rw-vnfd {
    prefix rw-vnfd;
  }
}
