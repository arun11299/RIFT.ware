/*
 * 
 * (c) Copyright RIFT.io, 2013-2016, All Rights Reserved
 *
 *
 */

module rw-vld-annotation
{
  namespace "http://riftio.com/ns/riftware-1.0/rw-vld-annotation";
  prefix "rw-vld-ann";

  import tailf-common {
    prefix tailf;
  }

  import rw-base {
    prefix rwbase;
  }

  import rw-vld {
    prefix rw-vld;
  }
}
