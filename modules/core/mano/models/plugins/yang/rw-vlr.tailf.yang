/*
 * 
 * (c) Copyright RIFT.io, 2013-2016, All Rights Reserved
 *
 *
 */

module rw-vlr-annotation
{
  namespace "http://riftio.com/ns/riftware-1.0/rw-vlr-annotation";
  prefix "rw-vlr-ann";

  import tailf-common {
    prefix tailf;
  }

  import rw-base {
    prefix rwbase;
  }

  import rw-vlr {
    prefix rw-vlr;
  }
}
