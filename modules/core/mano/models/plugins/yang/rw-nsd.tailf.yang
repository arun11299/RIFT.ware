/*
 * 
 * (c) Copyright RIFT.io, 2013-2016, All Rights Reserved
 *
 *
 */

module rw-nsd-annotation
{
  namespace "http://riftio.com/ns/riftware-1.0/rw-nsd-annotation";
  prefix "rw-nsd-ann";

  import tailf-common {
    prefix tailf;
  }

  import rw-base {
    prefix rwbase;
  }

  import rw-nsd {
    prefix rw-nsd;
  }
}
