/*
 * 
 * (c) Copyright RIFT.io, 2013-2016, All Rights Reserved
 *
 *
 */

module rw-config-agent-annotation
{
  namespace "http://riftio.com/ns/riftware-1.0/rw-config-agent-annotation";
  prefix "rw-config-agent-ann";

  import rw-config-agent {
    prefix rw-config-agent;
  }
}
